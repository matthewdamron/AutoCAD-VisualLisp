;;;;;;;;;;;;;;;;;;;;;;;;;;;;;;;;;;;;;;;;;;;;;;;;;;;;;;;;;;;;;;;;;;;;;;;;;;;;;;;;
;Begin c:FSDetail
;;;;;;;;;;;;;;;;;;;;;;;;;;;;;;;;;;;;;;;;;;;;;;;;;;;;;;;;;;;;;;;;;;;;;;;;;;;;;;;;
(defun c:FSDetail (/ *acdoc* origin entitytype entityname entitydatalist viewport viewportscale viewportheight viewportwidth viewportcenter_paper viewportviewtwistangle viewportcenter_model scalar viewporthandle_parent)
	(progn
		(if (= (getvar "tilemode") 0)
			(progn
				(if (>= (getvar "osmode") 16384)
					(progn
						(setq variable_list (list (list "cmdecho" 0 "osmode" (getvar "osmode") "clayer" "symbol" "CMLEADERSTYLE" "Fetzer -- Detail") T))
					)
					(progn
						(setq variable_list (list (list "cmdecho" 0 "osmode" 16384 "clayer" "symbol" "CMLEADERSTYLE" "Fetzer -- Detail") T))
					)
				)
				(environment variable_list)
				(setq *acdoc* (vla-get-ActiveDocument (vlax-get-acad-object)))
				(command "-layer" "on" "*" "")
				(command "-units" "2" "8" "1" "8" "0" "n")
				(command "graphscr")
				(setq origin (list 0.0 0.0 0.0))
				(setq entitytype "")
				(while (/= entitytype "VIEWPORT")
					(setq entityname (car (entsel "\nSelect parent viewport for FS Detail: ")))
					(setq entitydatalist (entget entityname '("ACAD")))
					(setq entitytype (cdr (assoc 0 entitydatalist)))
					(if (/= entitytype "VIEWPORT")
						(progn (prompt "\n*** Object selected is not a viewport. ***\n"))
					)
				)
				(command "vplayer" "freeze" "Veneer -- FS" "select" entityname "" "")
				(setq viewport (vlax-ename->vla-object entityname))
				(setq viewportscale (vlax-get-property viewport 'CustomScale))
				(setq viewportheight (vlax-get-property viewport 'Height))
				(setq viewportwidth (vlax-get-property viewport 'Width))
				(setq viewportcenter_paper (cdr (assoc 10 entitydatalist)))
				(setq viewportviewtwistangle (cdr (assoc 51 entitydatalist)))
				(setq viewportcenter_model (cdr (assoc 12 entitydatalist)))
				(if (and (= (car viewportcenter_model) 0.0) (= (cadr viewportcenter_model) 0.0) (= (caddr viewportcenter_model) 0.0))
					(progn (setq viewportcenter_model (cdr (nth 4 (cadr (assoc -3 entitydatalist))))))
				)
				(setq scalar (/ 1.0 viewportscale))
				(setq viewporthandle_parent (cdr (assoc 5 entitydatalist)))
				(detail_paper)
				(detail_model)
				(detailviewport)
				(restore variable_list)
			)
			(progn (alert "This command is only executable from paper space."))
		)
	)
	(gc)
	(princ)
)
;;;;;;;;;;;;;;;;;;;;;;;;;;;;;;;;;;;;;;;;;;;;;;;;;;;;;;;;;;;;;;;;;;;;;;;;;;;;;;;;
;End c:FSDetail
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin Detail_Paper
;;;;;;;;;;;;;;;;;;;;;;;;;;;;;;;;;;;;;;;;;;;;;;;;;;;;;;;;;;;;;;;;;;;;;;;;;;;;;;;;
(defun detail_paper (/)
	(setq detailwidth_paper 0.0)
	(setq detailheight_paper 0.0)
	(while (or (< detailwidth_paper (/ 3.0 16.0)) (< detailheight_paper (/ 3.0 16.0)))
		(setq detailpt1 (getpoint "\nDetail border start point:"))
		(setq detailpt2 (getcorner detailpt1 "\nDetail border end point:"))
		(setq detailcenter_paper (polar detailpt1 (angle detailpt1 detailpt2) (/ (distance detailpt1 detailpt2) 2)))
		(setq detailwidth_paper (abs (- (car detailpt1) (car detailpt2))))
		(setq detailheight_paper (abs (- (cadr detailpt1) (cadr detailpt2))))
		(if (or (< detailwidth_paper (/ 3.0 16.0)) (< detailheight_paper (/ 3.0 16.0)))
			(prompt "\n*** Detail border picked is too small. ***")
		)
	)
	(setq detailwidth_model (* scalar detailwidth_paper))
	(setq detailheight_model (* scalar detailheight_paper))
	(setq detailcorner1_paper (list (+ (car detailcenter_paper) (/ detailwidth_paper 2.0)) (+ (cadr detailcenter_paper) (/ detailheight_paper 2.0)) 0.0))
	(setq detailcorner2_paper (list (- (car detailcenter_paper) (/ detailwidth_paper 2.0)) (+ (cadr detailcenter_paper) (/ detailheight_paper 2.0)) 0.0))
	(setq detailcorner3_paper (list (- (car detailcenter_paper) (/ detailwidth_paper 2.0)) (- (cadr detailcenter_paper) (/ detailheight_paper 2.0)) 0.0))
	(setq detailcorner4_paper (list (+ (car detailcenter_paper) (/ detailwidth_paper 2.0)) (- (cadr detailcenter_paper) (/ detailheight_paper 2.0)) 0.0))
	(setq detailcorner1_model (trans detailcorner1_paper 1 0))
	(setq detailcorner2_model (trans detailcorner2_paper 1 0))
	(setq detailcorner3_model (trans detailcorner3_paper 1 0))
	(setq detailcorner4_model (trans detailcorner4_paper 1 0))
	(not (vla-put-MSpace *acdoc* :vlax-true))
	(not (vla-put-activePViewport *acdoc* viewport))
	(setq detailcorner1_model (trans (trans (trans detailcorner1_model 3 2) 2 1) 1 0))
	(setq detailcorner1_model (list (car detailcorner1_model) (cadr detailcorner1_model) 0.0))
	(setq detailcorner2_model (trans (trans (trans detailcorner2_model 3 2) 2 1) 1 0))
	(setq detailcorner2_model (list (car detailcorner2_model) (cadr detailcorner2_model) 0.0))
	(setq detailcorner3_model (trans (trans (trans detailcorner3_model 3 2) 2 1) 1 0))
	(setq detailcorner3_model (list (car detailcorner3_model) (cadr detailcorner3_model) 0.0))
	(setq detailcorner4_model (trans (trans (trans detailcorner4_model 3 2) 2 1) 1 0))
	(setq detailcorner4_model (list (car detailcorner4_model) (cadr detailcorner4_model) 0.0))
	(not (vla-put-MSpace *acdoc* :vlax-False))
	(setq pt1 (list (+ (car detailcenter_paper) (/ detailwidth_paper 2.0)) (+ (cadr detailcenter_paper) (- (/ detailheight_paper 2.0) (/ 1.0 16.0))) 0.0))
	(setq pt2 (list (+ (car detailcenter_paper) (- (/ detailwidth_paper 2.0) (/ 1.0 16.0))) (+ (cadr detailcenter_paper) (/ detailheight_paper 2.0))0.0))
	(setq pt3 (list (- (car detailcenter_paper) (- (/ detailwidth_paper 2.0) (/ 1.0 16.0))) (+ (cadr detailcenter_paper) (/ detailheight_paper 2.0)) 0.0))
	(setq pt4 (list (- (car detailcenter_paper) (/ detailwidth_paper 2.0)) (+ (cadr detailcenter_paper) (- (/ detailheight_paper 2.0) (/ 1.0 16.0))) 0.0))
	(setq pt5 (list (- (car detailcenter_paper) (/ detailwidth_paper 2.0)) (- (cadr detailcenter_paper) (- (/ detailheight_paper 2.0) (/ 1.0 16.0))) 0.0))
	(setq pt6 (list (- (car detailcenter_paper) (- (/ detailwidth_paper 2.0) (/ 1.0 16.0))) (- (cadr detailcenter_paper) (/ detailheight_paper 2.0)) 0.0))
	(setq pt7 (list (+ (car detailcenter_paper) (- (/ detailwidth_paper 2.0) (/ 1.0 16.0))) (- (cadr detailcenter_paper) (/ detailheight_paper 2.0)) 0.0))
	(setq pt8 (list (+ (car detailcenter_paper) (/ detailwidth_paper 2.0)) (- (cadr detailcenter_paper) (- (/ detailheight_paper 2.0) (/ 1.0 16.0))) 0.0))
	(setq arcmidpoint1 (polar (list (- (car pt1) (/ 1.0 16.0)) (cadr pt1) (caddr pt1)) (/ pi 4.0) (/ 1.0 16.0)))
	(setq arcmidpoint2 (polar (list (+ (car pt4) (/ 1.0 16.0)) (cadr pt4) (caddr pt4)) (/ (* 3.0 pi) 4.0) (/ 1.0 16.0)))
	(setq arcmidpoint3 (polar (list (+ (car pt5) (/ 1.0 16.0)) (cadr pt5) (caddr pt5)) (/ (* 5.0 pi) 4.0) (/ 1.0 16.0)))
	(setq arcmidpoint4 (polar (list (- (car pt8) (/ 1.0 16.0)) (cadr pt8) (caddr pt8)) (/ (* 7.0 pi) 4.0) (/ 1.0 16.0)))
	(setvar "PLINEWID" 0)
	(command "pline" pt1 "arc" "direction" detailcorner1_paper pt2 "line" pt3 "arc" "direction" detailcorner2_paper pt4 "line" pt5 "arc" "direction" detailcorner3_paper pt6 "line" pt7 "arc" "direction" detailcorner4_paper pt8 "line" pt1 "")
	(setq detailps_name (entlast))
	(command "pedit" detailps_name "close" "")
	(command "chprop" detailps_name "" "layer" "symbol" "ltype" "Fetzer -- Center" "")
	(setq detailps_handle (cdr (assoc 5 (entget detailps_name))))
	(if (= (getvar "userr4") 0)
		(progn (setvar "userr4" 65))
		(progn
			(if (or (= (getvar "userr4") 72) (= (getvar "userr4") 78))
				(progn (setvar "userr4" (+ (getvar "userr4") 2)))
				(progn (setvar "userr4" (+ (getvar "userr4") 1)))
			)
		)
	)
	(setq detailletter (chr (fix (getvar "userr4"))))
	(command "-insert" "SYM_DetailCallout" pause	"" "" "" detailletter "")
	(setq detail_name (entlast))
	(setq insertionpoint (getvar "lastpoint"))
	(command "erase" detail_name "")
	(if (> (car insertionpoint) (car detailcenter_paper))
		(progn
			(setq pt1 (list (- (car insertionpoint) 0.25) (cadr insertionpoint) (caddr insertionpoint)))
		)
		(progn
			(setq pt1 (list (+ (car insertionpoint) 0.25) (cadr insertionpoint) (caddr insertionpoint)))
		)
	)
	(setq dist 1.0e9)
	(if (< (distance pt1 arcmidpoint1) dist)
		(progn
			(setq arcmidpoint arcmidpoint1)
			(setq dist (distance pt1 arcmidpoint1))
		)
	)
	(if (< (distance pt1 arcmidpoint2) dist)
		(progn
			(setq arcmidpoint arcmidpoint2)
			(setq dist (distance pt1 arcmidpoint2))
		)
	)
	(if (< (distance pt1 arcmidpoint3) dist)
		(progn
			(setq arcmidpoint arcmidpoint3)
			(setq dist (distance pt1 arcmidpoint3))
		)
	)
	(if (< (distance pt1 arcmidpoint4) dist)
		(progn
			(setq arcmidpoint arcmidpoint4)
			(setq dist (distance pt1 arcmidpoint4))
		)
	)
	(command "mleader" "l" "c" insertionpoint detailletter "" arcmidpoint)
	(princ)
)
;;;;;;;;;;;;;;;;;;;;;;;;;;;;;;;;;;;;;;;;;;;;;;;;;;;;;;;;;;;;;;;;;;;;;;;;;;;;;;;;
;End Detail_Paper
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin Detail_Model
;;;;;;;;;;;;;;;;;;;;;;;;;;;;;;;;;;;;;;;;;;;;;;;;;;;;;;;;;;;;;;;;;;;;;;;;;;;;;;;;
(defun detail_model (/)
	(setvar "tilemode" 1)
	(command "'zoom" "extents")
	(command "'zoom" "0.9x")
	(command "'zoom" "window" detailcorner4_model detailcorner2_model)
	(command "'zoom" ".9x")
	(setvar "PLINEWID" 0)
	(command "pline" detailcorner1_model detailcorner2_model detailcorner3_model detailcorner4_model detailcorner1_model "")
	(setq detailms_name (entlast))
	(command "pedit" detailms_name "close" "")
	(command "chprop" detailms_name "" "layer" "viewport" "")
	(setq detailms_handle (cdr (assoc 5 (entget detailms_name))))
	(princ)
)
;;;;;;;;;;;;;;;;;;;;;;;;;;;;;;;;;;;;;;;;;;;;;;;;;;;;;;;;;;;;;;;;;;;;;;;;;;;;;;;;
;End Detail_Model
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin DetailViewport
;;;;;;;;;;;;;;;;;;;;;;;;;;;;;;;;;;;;;;;;;;;;;;;;;;;;;;;;;;;;;;;;;;;;;;;;;;;;;;;;
(defun detailviewport (/)
	(setvar "tilemode" 0)
	(command "pspace")
	(setq viewport_pt1 (list 42.9 0.24 0.0))
	(setq viewport_pt2 (list (+ 42.9 detailwidth_model) (+ 0.24 detailheight_model)))
	(command "-vports" viewport_pt1 viewport_pt2)
	(command "'zoom" "extents")
	(command "'zoom" ".9x")
	(setq entityname (entlast))
	(command "chprop" entityname "" "layer" "viewport" "")
	(command "vplayer" "freeze" "veneer,xplot" "select" entityname "" "")
	(command "-vports" "on" entityname "")
	(setq viewporthandle_child (cdr (assoc 5 (entget entityname))))
	(setq Viewport_Detail (vlax-ename->vla-object entityname))
	(vlax-put-property Viewport_Detail 'TwistAngle viewportviewtwistangle)
	(not (vla-put-MSpace *acdoc* :vlax-true))
	(not (vla-put-activePViewport *acdoc* Viewport_Detail))
	(command "'zoom" "window" detailcorner4_model detailcorner2_model)
	(command "regen")
	(not (vla-put-MSpace *acdoc* :vlax-False))
	(vlax-put-property Viewport_Detail 'CustomScale 1.0)
	(setq insertionpoint (list 42.9 -0.26 0.0))
	(command "-insert" "SYM_DetailTitle" insertionpoint "" "" "" detailletter "" "" "" "")
	(command "chprop" "last" "" "layer" "symbol" "")
	(setq detaillinesymbol (entlast))
	(princ)
)
;;;;;;;;;;;;;;;;;;;;;;;;;;;;;;;;;;;;;;;;;;;;;;;;;;;;;;;;;;;;;;;;;;;;;;;;;;;;;;;;
;End DetailViewport
;;;;;;;;;;;;;;;;;;;;;;;;;;;;;;;;;;;;;;;;;;;;;;;;;;;;;;;;;;;;;;;;;;;;;;;;;;;;;;;;
