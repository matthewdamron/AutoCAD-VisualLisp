;;;;;;;;;;;;;;;;;;;;;;;;;;;;;;;;;;;;;;;;;;;;;;;;;;;;;;;;;;;;;;;;;;;;;;;;;;;;;;;;
;Begin c:DimensionTextReset
;;;;;;;;;;;;;;;;;;;;;;;;;;;;;;;;;;;;;;;;;;;;;;;;;;;;;;;;;;;;;;;;;;;;;;;;;;;;;;;;
(defun c:DimensionTextReset (/ entitytype entity entityname entitydatalist)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension to clear text: "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension to clear text: "))
						(if (= (getvar "errno") 7)
							(prompt "\nNothing selected.")
						)
					)
					(setq entityname (car entity))
					(setq entitydatalist (entget entityname))
					(setq entitytype (cdr (assoc 0 entitydatalist)))
				)
				(setq entitydatalist (subst (cons 1 "") (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionTextReset
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionVerifyInField
;;;;;;;;;;;;;;;;;;;;;;;;;;;;;;;;;;;;;;;;;;;;;;;;;;;;;;;;;;;;;;;;;;;;;;;;;;;;;;;;
(defun c:DimensionVerifyInField (/ i entity entityname entitydatalist entitytype dimtext strl strposition)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension for \"VIF\": "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension for \"VIF\": "))
						(if (= (getvar "errno") 7)
							(prompt "\nNothing selected.")
						)
					)
					(setq entityname (car entity))
					(setq entitydatalist (entget entityname))
					(setq entitytype (cdr (assoc 0 entitydatalist)))
				)
				(setq dimtext (cdr (assoc 1 entitydatalist)))
				(setq strl (strlen dimtext))
				(if (= strl 0)
					(setq dimtext "VIF <>")
				)
				(if (> strl 0)
					(progn
						(setq strposition (vl-string-search "<" dimtext))
						(setq dimtext (substr dimtext (+ strposition 1)))
						(setq dimtext (strcat "VIF " dimtext))
					)
				)
				(setq entitydatalist (subst (cons 1 dimtext) (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionVerifyInField
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionHoldTo
;;;;;;;;;;;;;;;;;;;;;;;;;;;;;;;;;;;;;;;;;;;;;;;;;;;;;;;;;;;;;;;;;;;;;;;;;;;;;;;;
(defun c:DimensionHoldTo (/ i entity entityname entitydatalist entitytype dimtext strl strposition)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension for \"HOLD TO\": "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension for \"HOLD TO\": "))
						(if (= (getvar "errno") 7)
							(prompt "\nNothing selected.")
						)
					)
					(setq entityname (car entity))
					(setq entitydatalist (entget entityname))
					(setq entitytype (cdr (assoc 0 entitydatalist)))
				)
				(setq dimtext (cdr (assoc 1 entitydatalist)))
				(setq strl (strlen dimtext))
				(if (= strl 0)
					(setq dimtext "HOLD <>")
				)
				(if (> strl 0)
					(progn
						(setq strposition (vl-string-search "<" dimtext))
						(setq dimtext (substr dimtext (+ strposition 1) (- (strlen dimtext) strposition)))
						(setq dimtext (strcat "HOLD " dimtext))
					)
				)
				(setq entitydatalist (subst (cons 1 dimtext) (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionHoldTo
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionAboveRoughFloor
;;;;;;;;;;;;;;;;;;;;;;;;;;;;;;;;;;;;;;;;;;;;;;;;;;;;;;;;;;;;;;;;;;;;;;;;;;;;;;;;
(defun c:DimensionAboveRoughFloor (/ i entity entityname entitydatalist entitytype dimtext strl strposition)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension for \"ARF\": "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension for \"ARF\": "))
						(if (= (getvar "errno") 7)
							(prompt "\nNothing selected.")
						)
					)
					(setq entityname (car entity))
					(setq entitydatalist (entget entityname))
					(setq entitytype (cdr (assoc 0 entitydatalist)))
				)
				(setq dimtext (cdr (assoc 1 entitydatalist)))
				(setq strl (strlen dimtext))
				(if (= strl 0)
					(setq dimtext "<> ARF")
				)
				(if (> strl 0)
					(progn
						(setq strposition (vl-string-search ">" dimtext))
						(setq dimtext (substr dimtext 1 (+ strposition 1)))
						(setq dimtext (strcat dimtext " ARF"))
					)
				)
				(setq entitydatalist (subst (cons 1 dimtext) (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionAboveRoughFloor
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionAboveFinishedFloor
;;;;;;;;;;;;;;;;;;;;;;;;;;;;;;;;;;;;;;;;;;;;;;;;;;;;;;;;;;;;;;;;;;;;;;;;;;;;;;;;
(defun c:DimensionAboveFinishedFloor (/ i entity entityname entitydatalist entitytype dimtext strl strposition)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension for \"AFF\": "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension for \"AFF\": "))
						(if (= (getvar "errno") 7)
							(prompt "\nNothing selected.")
						)
					)
					(setq entityname (car entity))
					(setq entitydatalist (entget entityname))
					(setq entitytype (cdr (assoc 0 entitydatalist)))
				)
				(setq dimtext (cdr (assoc 1 entitydatalist)))
				(setq strl (strlen dimtext))
				(if (= strl 0)
					(setq dimtext "<> AFF")
				)
				(if (> strl 0)
					(progn
						(setq strposition (vl-string-search ">" dimtext))
						(setq dimtext (substr dimtext 1 (+ strposition 1)))
						(setq dimtext (strcat dimtext " AFF"))
					)
				)
				(setq entitydatalist (subst (cons 1 dimtext) (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionAboveFinishedFloor
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionClearOpening
;;;;;;;;;;;;;;;;;;;;;;;;;;;;;;;;;;;;;;;;;;;;;;;;;;;;;;;;;;;;;;;;;;;;;;;;;;;;;;;;
(defun c:DimensionClearOpening (/ i entity entityname entitydatalist entitytype dimtext strl strposition)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension for \"CLEAR\": "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension for \"CLEAR\": "))
						(if (= (getvar "errno") 7)
							(prompt "\nNothing selected.")
						)
					)
					(setq entityname (car entity))
					(setq entitydatalist (entget entityname))
					(setq entitytype (cdr (assoc 0 entitydatalist)))
				)
				(setq dimtext (cdr (assoc 1 entitydatalist)))
				(setq strl (strlen dimtext))
				(if (= strl 0)
					(setq dimtext "<> CLEAR")
				)
				(if (> strl 0)
					(progn
						(setq strposition (vl-string-search ">" dimtext))
						(setq dimtext (substr dimtext 1 (+ strposition 1)))
						(setq dimtext (strcat dimtext " CLEAR"))
					)
				)
				(setq entitydatalist (subst (cons 1 dimtext) (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionClearOpening
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionVerified
;;;;;;;;;;;;;;;;;;;;;;;;;;;;;;;;;;;;;;;;;;;;;;;;;;;;;;;;;;;;;;;;;;;;;;;;;;;;;;;;
(defun c:DimensionVerified (/ i entity entityname entitydatalist entitytype dimtext strl strposition)
	(if (>= (getvar "osmode") 16384)
		(progn (setq variable_list (list (list "cmdecho" 0 "osmode" (getvar "osmode")))))
		(progn (setq variable_list (list (list "cmdecho" 0 "osmode" 16384))))
	)
	(environment variable_list)
	(setq i 0)
	(while (< i 1)
		(setvar "errno" 7)
		(while (= (getvar "errno") 7)
			(setvar "errno" 0)
			(setq entity (entsel "\nSelect dimension for checkmark: "))
			(if (= (getvar "errno") 7)
				(prompt "\nNothing selected.")
			)
		)
		(if (= entity nil)
			(progn (setq i 1))
			(progn
				(setq entityname (car entity))
				(setq entitydatalist (entget entityname))
				(setq entitytype (cdr (assoc 0 entitydatalist)))
				(while (/= entitytype "DIMENSION")
					(prompt "\nObject selected is not a dimension. ")
					(setvar "errno" 7)
					(while (= (getvar "errno") 7)
						(setvar "errno" 0)
						(setq entity (entsel "\nSelect dimension for checkmark: "))
						(if (= (getvar "errno") 7)
							(prompt "\nNothing selected.")
						)
					)
					(setq entityname (car entity))
					(setq entitydatalist (entget entityname))
					(setq entitytype (cdr (assoc 0 entitydatalist)))
				)
				(setq dimtext (cdr (assoc 1 entitydatalist)))
				(setq strl (strlen dimtext))
				(if	(> strl 0)
					(progn
						(setq strposition (vl-string-search "<" dimtext))
						(setq dimtext (substr dimtext (+ strposition 1)))
						(setq dimtext (strcat "{\\fWingdings|b1|i0|c2|p2;ü\\fMS Shell Dlg|b0|i0|c0|p0;\\C256;} " dimtext))
					)
					(progn
						(setq dimtext (strcat "{\\fWingdings|b1|i0|c2|p2;ü\\fMS Shell Dlg|b0|i0|c0|p0;\\C256;} <>"))
					)
				)
				(setq entitydatalist (subst (cons 1 dimtext) (assoc 1 entitydatalist) entitydatalist))
				(entmod entitydatalist)
			)
		)
	)
	(restore variable_list)
	(gc)
	(princ)
)
;;;;;;;;;;;;;;;;;;;;;;;;;;;;;;;;;;;;;;;;;;;;;;;;;;;;;;;;;;;;;;;;;;;;;;;;;;;;;;;;
;End c:DimensionVerified
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionCenterlineSymbol
;;;;;;;;;;;;;;;;;;;;;;;;;;;;;;;;;;;;;;;;;;;;;;;;;;;;;;;;;;;;;;;;;;;;;;;;;;;;;;;;
(defun c:DimensionCenterlineSymbol (/ insertionpoint1 i)
	(progn
		(setq variable_list (list (list "cmdecho" 0 "osmode" 1)))
		(environment variable_list)
		(setq i 0)
		(while (< i 1)
			(initget "eXit")
			(setq insertionpoint1 (getpoint "Specify insertion point for center line symbol <eXit>: "))
			(if (/= insertionpoint1 nil)
				(progn
					(if	(/= insertionpoint1 "eXit")
						(progn
							(command "-insert" "SYM_Centerline" insertionpoint1 "" "" pause)
							(command "chprop" "last" "" "layer" "dimension" "")
						)
						(progn (setq i (+ i 1)))
					)
				)
				(progn (setq i (+ i 1)))
			)
		)
		(restore variable_list)
	)
	(princ)
)
;;;;;;;;;;;;;;;;;;;;;;;;;;;;;;;;;;;;;;;;;;;;;;;;;;;;;;;;;;;;;;;;;;;;;;;;;;;;;;;;
;End c:DimensionCenterlineSymbol
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionArcLength
;;;;;;;;;;;;;;;;;;;;;;;;;;;;;;;;;;;;;;;;;;;;;;;;;;;;;;;;;;;;;;;;;;;;;;;;;;;;;;;;
(defun c:DimensionArcLength (/ tab e_name e_datalist e_type z I dimension_type measurement point1 point2 point3 radius ss viewport_name viewport_datalist viewport customscale center height width upper_right_corner lower_left_corner s inches j k dimtxt feet in fraction n d r nx dx dimension)
	(progn
		(setq variable_list (list (list "cmdecho" 0)))
		(environment variable_list)
		(command "-layer" "on" "dimension" "")
		(setq tab (vla-get-name (vla-get-activelayout (vla-get-ActiveDocument (vlax-get-Acad-Object)))))
		(command "dimangular" pause pause)
		(setq e_name (entlast))
		(setq e_datalist (entget e_name))
		(setq e_type (cdr (assoc 0 e_datalist)))
		(if (= e_type "DIMENSION")
			(progn
				(if (= (cdr (last e_datalist)) "AcDbRotatedDimension")
					(progn
						(setq z (list))
						(setq I 0)
						(while (< I (- (length e_datalist) 1))
							(setq z (append z (list (nth I e_datalist))))
							(setq I (+ I 1))
						)
						(setq dimension_type (cdr (assoc 100 (reverse z))))
					)
					(progn
						(setq dimension_type (cdr (assoc 100 (reverse e_datalist))))
					)
				)
				(if (= dimension_type "AcDb3PointAngularDimension")
					(progn
						(setq measurement (cdr (assoc 42 e_datalist)))
						(setq point1 (cdr (assoc 13 e_datalist)))
						(setq point2 (cdr (assoc 14 e_datalist)))
						(setq point3 (cdr (assoc 15 e_datalist)))
						(setq radius (distance point1 point3))
						(setq ss nil)
						(setq ss (ssget "X" (list (cons -4 "<AND") (cons 0 "VIEWPORT") (cons 410 tab) (cons -4 "AND>"))))
							(if ss
								(progn
									(setq I 0)
									(while (< I (sslength ss))
										(setq viewport_name (ssname ss I))
										(setq viewport_datalist (entget viewport_name))
										(setq viewport (vlax-ename->vla-object viewport_name))
										(setq customscale (vlax-get-property viewport 'CustomScale))
										(setq center	(list	(vlax-safearray-get-element (vlax-variant-value (vlax-get-property viewport 'Center)) 0)
																(vlax-safearray-get-element (vlax-variant-value (vlax-get-property viewport 'Center)) 1)
																(vlax-safearray-get-element (vlax-variant-value (vlax-get-property viewport 'Center)) 2)
														)
										)
										(setq height (vlax-get-property viewport 'Height))
										(setq width (vlax-get-property viewport 'Width))
										(setq upper_right_corner (list (+ (car center) (/ width 2.0)) (+ (cadr center) (/ height 2.0)) 0.0))
										(setq lower_left_corner (list (- (car center) (/ width 2.0)) (- (cadr center) (/ height 2.0)) 0.0))
										(if (and	(<= (car point1) (car upper_right_corner)) (<= (cadr point1) (cadr upper_right_corner))
													(<= (car point2) (car upper_right_corner)) (<= (cadr point2) (cadr upper_right_corner))
													(>= (car point1) (car lower_left_corner)) (>= (cadr point1) (cadr lower_left_corner))
													(>= (car point2) (car lower_left_corner)) (>= (cadr point2) (cadr lower_left_corner))
											)
											(progn
												(setq I (sslength ss))
												(setq radius (/ (distance point1 point3) customscale))
											)
										)
										(setq I (+ I 1))
									)
								)
							)
							(setq s (* measurement radius))
							(setq inches s)
							(setq i 0.015625)
							(setq j (/ inches i))
							(setq k (fix j))
							(if (/= (- j k) 0.0)
								(progn
									(if (< (- j k) 0.4)
										(progn (setq inches (* k i)))
											(progn
												(setq k (+ k 1.0))
												(setq inches (* k i))
											)
									)
								)
								(progn
									(setq inches inches)
								)
							)
							(if (>= inches 144.0)
								(progn
									(setq s (rtos inches 2 4))
									(setq dimtxt (strcat "AL " s))
									(setq dimtxt (strcat dimtxt "\""))
									(setq feet (fix (/ (fix inches) 12.0)))
									(setq in (* (- (/ (fix inches) 12.0) (fix (/ (fix inches) 12.0))) 12.0))
									(setq fraction ( / (- inches (fix inches)) i))
									(if (/= 0 fraction)
										(progn
											(setq n 1.0)
											(setq d 128.0)
											(while (/= n 64.0)
												(setq n (* n 2))
												(setq d (/ d 2))
												(setq r (rem fraction n))
												(if (/= r 0)
													(progn
														(setq nx (/ fraction (/ n 2)))
														(setq dx d)
														(setq n 64.0)
													)
												)
											)
											(setq dimtxt (strcat dimtxt " [" (rtos feet) "'-" (rtos in) " " (rtos nx) "/" (rtos dx) "\"" "]"))
										)
										(setq dimtxt (strcat dimtxt " [" (rtos feet) "'-" (rtos in) "\"" "]"))
									)
								)
								(progn
									(setq s (rtos inches 2 4))
									(setq dimtxt (strcat "AL " s))
									(setq dimtxt (strcat dimtxt "\""))
								)
							)
							(setq dimension (vlax-ename->vla-object e_name))
							(vlax-put-property dimension 'TextOverride dimtxt)
							(vlax-put-property dimension 'TextColor 253)
							(vlax-put-property dimension 'Arrowhead1Type acArrowOblique)
							(vlax-put-property dimension 'Arrowhead2Type acArrowOblique)
							(vlax-put-property dimension 'TextInsideAlign :vlax-false)
					)
				)
			)
		)
	)
	(setq ss nil)
	(gc)
	(restore variable_list)
	(princ)
)
;;;;;;;;;;;;;;;;;;;;;;;;;;;;;;;;;;;;;;;;;;;;;;;;;;;;;;;;;;;;;;;;;;;;;;;;;;;;;;;;
;End c:DimensionArcLength
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionHome
;;;;;;;;;;;;;;;;;;;;;;;;;;;;;;;;;;;;;;;;;;;;;;;;;;;;;;;;;;;;;;;;;;;;;;;;;;;;;;;;
(defun c:DimensionHome (/ entitytype entity entityname entitydatalist)
	(if (>= (getvar "osmode") 16384)
		(progn (setq variable_list (list (list "cmdecho" 0 "osmode" (getvar "osmode")))))
		(progn (setq variable_list (list (list "cmdecho" 0 "osmode" 16384))))
	)
	(environment variable_list)
	(setq entitytype "")
	(while (/= entitytype "DIMENSION")
		(setvar "errno" 7)
		(while (= (getvar "errno") 7)
			(setvar "errno" 0)
			(setq entity (entsel "\nSelect dimension to send home: "))
			(if (= (getvar "errno") 7)
				(prompt "\nNothing selected.")
			)
		)
		(setq entityname (car entity))
		(setq entitydatalist (entget entityname))
		(setq entitytype (cdr (assoc 0 entitydatalist)))
		(if	(/= entitytype "DIMENSION")
			(prompt "\nObject selected is not a dimension. ")
		)
	)
	(command "dimedit" "home" entity "")
	(restore variable_list)
	(gc)
	(princ)
)
;;;;;;;;;;;;;;;;;;;;;;;;;;;;;;;;;;;;;;;;;;;;;;;;;;;;;;;;;;;;;;;;;;;;;;;;;;;;;;;;
;End c:DimensionHome
;;;;;;;;;;;;;;;;;;;;;;;;;;;;;;;;;;;;;;;;;;;;;;;;;;;;;;;;;;;;;;;;;;;;;;;;;;;;;;;;

;;;;;;;;;;;;;;;;;;;;;;;;;;;;;;;;;;;;;;;;;;;;;;;;;;;;;;;;;;;;;;;;;;;;;;;;;;;;;;;;
;Begin c:DimensionHomeM
;;;;;;;;;;;;;;;;;;;;;;;;;;;;;;;;;;;;;;;;;;;;;;;;;;;;;;;;;;;;;;;;;;;;;;;;;;;;;;;;
(defun c:DimensionHomeM	(/ i ss1 ss1l)
	(if (>= (getvar "osmode") 16384)
		(progn (setq variable_list (list (list "cmdecho" 0 "osmode" (getvar "osmode")))))
		(progn (setq variable_list (list (list "cmdecho" 0 "osmode" 16384))))
	)
	(environment variable_list)
	(setq i 0)
	(setq ss1 (ssget '((0 . "DIMENSION"))))
	(if ss1
		(progn
			(setq ss1l (sslength ss1))
			(while (< i ss1l) (command "dimedit" "home" (ssname ss1 i) "") (setq i (+ i 1)))
		)
	)
	(setq ss1 nil)
	(restore variable_list)
	(gc)
	(princ)
)
;;;;;;;;;;;;;;;;;;;;;;;;;;;;;;;;;;;;;;;;;;;;;;;;;;;;;;;;;;;;;;;;;;;;;;;;;;;;;;;;
;End c:DimensionHomeM
;;;;;;;;;;;;;;;;;;;;;;;;;;;;;;;;;;;;;;;;;;;;;;;;;;;;;;;;;;;;;;;;;;;;;;;;;;;;;;;;
